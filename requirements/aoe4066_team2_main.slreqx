# aoe4066_team2_main

## #1: Airport Infrastructure Compatibility (Functional)
Aircraft shall be compatible with airports it provides services to.

### #3: Minimum Runway Length (Functional)
Aircraft minimum runway length shall be greater than or equal to 8000ft.

### #4: Gate Compatibility (Functional)
Aircraft shall comply with FAA Aircraft Design Group V (ADG V) or ICAO Code E.

### #5: Taxiway Design Group (Functional)
Aircraft shall operate at airports with taxiways no larger than what is specified in TDG 6.

## #6: Cruise Speed (Functional)
Sustained Cruise Mach shall be 1.7

## #7: Payload (Functional)
Aircraft shall have a minimum payload of 70 passengers (220 lbs each)

## #8: Range (Functional)
Aircraft range shall be 4000 nautical miles.

## #9: Noise Compliance (Functional)
Aircraft must comply with associated noise restrictions.

### #11: Airport communitiy noise (Functional)
ICAO Chapter 14 limits, with margin (Alternatively, FAA 14 CFR Part 36)

### #12: Sonic Boom (Functional)
Overland sonic boom <75 EPNL

## #10: Certification and Entry Into Service (Functional)

### #13: Certification Standards (Functional)
Must meet 14 CFR Part 25 (or equivalent international) certification standards. https://www.ecfr.gov/current/title-14/chapter-I/subchapter-C/part-25?toc=1

#### #26: Controllability (Functional)
The airplane must be safely controllable and maneuverable during takeoff, climb, level flight, descent, and landing.

#### #27: Flight Condition Transition (Functional)
It must be possible to make a smooth transition from one flight condition to any other flight condition without exceptional piloting skill, alertness, or strength, and without danger of exceeding the airplane limit-load factor under any probable operating conditions, including:
1. The sudden failure of the critical engine;
2. For airplanes with three or more engines, the sudden failure of the second critical engine when the airplane is in the en route, approach, or landing configuration and is trimmed with the critical engine inoperative; and
3. Configuration changes, including deployment or retraction of deceleration devices.

#### #28: Safely controllable with ice accretion (Functional)
The airplane must be shown to be safely controllable and maneuverable with the most critical of the ice accretion(s) appropriate to the phase of flight as defined in Appendices C and O of this part, as applicable, in accordance with § 25.21(g), and with the critical engine inoperative and its propeller (if applicable) in the minimum drag position:
1. At the minimum V2 for takeoff;
2. During an approach and go-around; and
3. During an approach and landing.

#### #29: Maximum Control Forces (Functional)
The following table prescribes, for conventional wheel type controls, the maximum control forces permitted during the testing required by paragraph (a) through (c) of this section:
| Force, in pounds, applied to the control wheel or rudder pedals | Pitch | Roll | Yaw |
| --- | --- | --- | --- |
| For short term application for pitch and roll control—two hands available for control | 75 | 50 |  |
| --- | --- | --- | --- |
| For short term application for pitch and roll control—one hand available for control | 50 | 25 |  |
| For short term application for yaw control |  |  | 150 |
| For long term application | 10 | 5 | 20 |
Approved operating procedures or conventional operating practices must be followed when demonstrating compliance with the control force limitations for short term application that are prescribed in paragraph (d) of this section. The airplane must be in trim, or as near to being in trim as practical, in the preceding steady flight condition. For the takeoff condition, the airplane must be trimmed according to the approved operating procedures.
When demonstrating compliance with the control force limitations for long term application that are prescribed in paragraph (d) of this section, the airplane must be in trim, or as near to being in trim as practical
When maneuvering at a constant airspeed or Mach number (up to VFC/MFC), the stick forces and the gradient of the stick force versus maneuvering load factor must lie within satisfactory limits. The stick forces must not be so great as to make excessive demands on the pilot's strength when maneuvering the airplane, and must not be so low that the airplane can easily be overstressed inadvertently. Changes of gradient that occur with changes of load factor must not cause undue difficulty in maintaining control of the airplane, and local gradients must not be so low as to result in a danger of overcontrolling.

#### #30: Constant Speed Maneuvering Capabilities (Functional)
The maneuvering capabilities in a constant speed coordinated turn at forward center of gravity, as specified in the following table, must be free of stall warning or other characteristics that might interfere with normal maneuvering:
| Configuration | Speed | Maneuvering bank angle in a coordinated turn | Thrust/power setting |
| --- | --- | --- | --- |
| Takeoff | V 2 | 30° | Asymmetric WAT-Limited. 1 |
| --- | --- | --- | --- |
| Takeoff | 2 V 2 + XX | 40° | All-engines-operating climb. 3 |
| En route | V FTO | 40° | Asymmetric WAT-Limited. 1 |
| Landing | V REF | 40° | Symmetric for −3° flight path angle. |
| 1 A combination of weight, altitude, and temperature (WAT) such that the thrust or power setting produces the minimum climb gradient specified in § 25.121 for the flight condition. |  |  |  |
| --- | --- | --- | --- |
| 2 Airspeed approved for all-engines-operating initial climb. |  |  |  |
| 3 That thrust or power setting which, in the event of failure of the critical engine and without any crew action to adjust the thrust or power of the remaining engines, would result in the thrust or power specified for the takeoff condition at V2, or any lesser thrust or power setting that is used for all-engines-operating initial climb procedures. |  |  |  |

#### #34: Load Distribution Limits (Functional)
(a) Ranges of weights and centers of gravity within which the airplane may be safely operated must be established. If a weight and center of gravity combination is allowable only within certain load distribution limits (such as spanwise) that could be inadvertently exceeded, these limits and the corresponding weight and center of gravity combinations must be established.
(b) The load distribution limits may not exceed—
(1) The selected limits;
(2) The limits at which the structure is proven; or
(3) The limits at which compliance with each applicable flight requirement of this subpart is shown.

#### #38: Stall Speed (Functional)
(a) The reference stall speed, VSR, is a calibrated airspeed defined by the applicant. VSR may not be less than a 1-g stall speed. VSR is expressed as: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
where:
VCLMAX = Calibrated airspeed obtained when the load factor-corrected lift coefficient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
is first a maximum during the maneuver prescribed in paragraph (c) of this section. In addition, when the maneuver is limited by a device that abruptly pushes the nose down at a selected angle of attack (e.g., a stick pusher), VCLMAX may not be less than the speed existing at the instant the device operates;
nZW = Load factor normal to the flight path at VCLMAX
W = Airplane gross weight;
S = Aerodynamic reference wing area; and
q = Dynamic pressure.
(b) VCLMAX is determined with:
(1) Engines idling, or, if that resultant thrust causes an appreciable decrease in stall speed, not more than zero thrust at the stall speed;
(2) Propeller pitch controls (if applicable) in the takeoff position;
(3) The airplane in other respects (such as flaps, landing gear, and ice accretions) in the condition existing in the test or performance standard in which VSR is being used;
(4) The weight used when VSR is being used as a factor to determine compliance with a required performance standard;
(5) The center of gravity position that results in the highest value of reference stall speed; and
(6) The airplane trimmed for straight flight at a speed selected by the applicant, but not less than 1.13VSR and not greater than 1.3VSR.
(c) Starting from the stabilized trim condition, apply the longitudinal control to decelerate the airplane so that the speed reduction does not exceed one knot per second.
(d) In addition to the requirements of paragraph (a) of this section, when a device that abruptly pushes the nose down at a selected angle of attack (e.g., a stick pusher) is installed, the reference stall speed, VSR, may not be less than 2 knots or 2 percent, whichever is greater, above the speed at which the device operates.

#### #39: Takeoff Speed (Functional)
(a) V1 must be established in relation to VEF as follows:
(1) VEF is the calibrated airspeed at which the critical engine is assumed to fail. VEF must be selected by the applicant, but may not be less than VMCG determined under § 25.149(e).
(2) V1, in terms of calibrated airspeed, is selected by the applicant; however, V1 may not be less than VEF plus the speed gained with critical engine inoperative during the time interval between the instant at which the critical engine is failed, and the instant at which the pilot recognizes and reacts to the engine failure, as indicated by the pilot's initiation of the first action (e.g., applying brakes, reducing thrust, deploying speed brakes) to stop the airplane during accelerate-stop tests.
(b) V2MIN, in terms of calibrated airspeed, may not be less than—
(1) 1.13 VSR for—
(i) Two-engine and three-engine turbopropeller and reciprocating engine powered airplanes; and
(ii) Turbojet powered airplanes without provisions for obtaining a significant reduction in the one-engine-inoperative power-on stall speed;
(2) 1.08 VSR for—
(i) Turbopropeller and reciprocating engine powered airplanes with more than three engines; and
(ii) Turbojet powered airplanes with provisions for obtaining a significant reduction in the one-engine-inoperative power-on stall speed; and
(3) 1.10 times VMC established under § 25.149.
(c) V2 , in terms of calibrated airspeed, must be selected by the applicant to provide at least the gradient of climb required by § 25.121(b) but may not be less than—
(1) V2MIN;
(2) VR plus the speed increment attained (in accordance with § 25.111(c)(2)) before reaching a height of 35 feet above the takeoff surface; and
(3) A speed that provides the maneuvering capability specified in § 25.143(h).
(d) VMU is the calibrated airspeed at and above which the airplane can safely lift off the ground, and con- tinue the takeoff. VMU speeds must be selected by the applicant throughout the range of thrust-to-weight ratios to be certificated. These speeds may be established from free air data if these data are verified by ground takeoff tests.
(e) VR, in terms of calibrated airspeed, must be selected in accordance with the conditions of paragraphs (e)(1) through (4) of this section:
(1) VR may not be less than—
(i) V1 ;
(ii) 105 percent of VMC;
(iii) The speed (determined in accordance with § 25.111(c)(2)) that allows reaching V2 before reaching a height of 35 feet above the takeoff surface; or
(iv) A speed that, if the airplane is rotated at its maximum practicable rate, will result in a VLOF of not less than —
(A) 110 percent of VMU in the all-engines-operating condition, and 105 percent of VMU determined at the thrust-to-weight ratio corresponding to the one-engine-inoperative condition; or
(B) If the VMU attitude is limited by the geometry of the airplane (i.e., tail contact with the runway), 108 percent of VMU in the all-engines-operating condition, and 104 percent of VMU determined at the thrust-to-weight ratio corresponding to the one-engine-inoperative condition.
(2) For any given set of conditions (such as weight, configuration, and temperature), a single value of VR, obtained in accordance with this paragraph, must be used to show compliance with both the one-engine-inoperative and the all-engines-operating takeoff provisions.
(3) It must be shown that the one-engine-inoperative takeoff distance, using a rotation speed of 5 knots less than VR established in accordance with paragraphs (e)(1) and (2) of this section, does not exceed the corresponding one-engine-inoperative takeoff distance using the established VR. The takeoff distances must be determined in accordance with § 25.113(a)(1).
(4) Reasonably expected variations in service from the established takeoff procedures for the operation of the airplane (such as over-rotation of the airplane and out-of-trim conditions) may not result in unsafe flight characteristics or in marked increases in the scheduled takeoff distances established in accordance with § 25.113(a).
(f) VLOF is the calibrated airspeed at which the airplane first becomes airborne.
(g) VFTO , in terms of calibrated airspeed, must be selected by the applicant to provide at least the gradient of climb required by § 25.121(c), but may not be less than—
(1) 1.18 VSR; and
(2) A speed that provides the maneuvering capability specified in § 25.143(h).
(h) In determining the takeoff speeds V1, VR, and V2 for flight in icing conditions, the values of VMCG, VMC, and VMU determined for non-icing conditions may be used.

#### #40: Takeoff Path (Functional)
(a) The takeoff path extends from a standing start to a point in the takeoff at which the airplane is 1,500 feet above the takeoff surface, or at which the transition from the takeoff to the en route configuration is completed and VFTO is reached, whichever point is higher. In addition—
(1) The takeoff path must be based on the procedures prescribed in § 25.101(f);
(2) The airplane must be accelerated on the ground to VEF, at which point the critical engine must be made inoperative and remain inoperative for the rest of the takeoff; and
(3) After reaching VEF, the airplane must be accelerated to V2.
(b) During the acceleration to speed V2, the nose gear may be raised off the ground at a speed not less than VR. However, landing gear retraction may not be begun until the airplane is airborne.
(c) During the takeoff path determination in accordance with paragraphs (a) and (b) of this section—
(1) The slope of the airborne part of the takeoff path must be positive at each point;
(2) The airplane must reach V2 before it is 35 feet above the takeoff surface and must continue at a speed as close as practical to, but not less than V2, until it is 400 feet above the takeoff surface;
(3) At each point along the takeoff path, starting at the point at which the airplane reaches 400 feet above the takeoff surface, the available gradient of climb may not be less than—
(i) 1.2 percent for two-engine airplanes;
(ii) 1.5 percent for three-engine airplanes; and
(iii) 1.7 percent for four-engine airplanes.
(4) The airplane configuration may not be changed, except for gear retraction and automatic propeller feathering, and no change in power or thrust that requires action by the pilot may be made until the airplane is 400 feet above the takeoff surface; and
(5) If § 25.105(a)(2) requires the takeoff path to be determined for flight in icing conditions, the airborne part of the takeoff must be based on the airplane drag:
(i) With the most critical of the takeoff ice accretion(s) defined in Appendices C and O of this part, as applicable, in accordance with § 25.21(g), from a height of 35 feet above the takeoff surface up to the point where the airplane is 400 feet above the takeoff surface; and
(ii) With the most critical of the final takeoff ice accretion(s) defined in Appendices C and O of this part, as applicable, in accordance with § 25.21(g), from the point where the airplane is 400 feet above the takeoff surface to the end of the takeoff path.
(d) The takeoff path must be determined by a continuous demonstrated takeoff or by synthesis from segments. If the takeoff path is determined by the segmental method—
(1) The segments must be clearly defined and must be related to the distinct changes in the configuration, power or thrust, and speed;
(2) The weight of the airplane, the configuration, and the power or thrust must be constant throughout each segment and must correspond to the most critical condition prevailing in the segment;
(3) The flight path must be based on the airplane's performance without ground effect; and
(4) The takeoff path data must be checked by continuous demonstrated takeoffs up to the point at which the airplane is out of ground effect and its speed is stabilized, to ensure that the path is conservative relative to the continous path.
The airplane is considered to be out of the ground effect when it reaches a height equal to its wing span.
(e) For airplanes equipped with standby power rocket engines, the takeoff path may be determined in accordance with section II of appendix E.

#### #41: Takeoff Distance/Run (Functional)
(a) Takeoff distance on a dry runway is the greater of—
(1) The horizontal distance along the takeoff path from the start of the takeoff to the point at which the airplane is 35 feet above the takeoff surface, determined under § 25.111 for a dry runway; or
(2) 115 percent of the horizontal distance along the takeoff path, with all engines operating, from the start of the takeoff to the point at which the airplane is 35 feet above the takeoff surface, as determined by a procedure consistent with § 25.111.
(b) Takeoff distance on a wet runway is the greater of—
(1) The takeoff distance on a dry runway determined in accordance with paragraph (a) of this section; or
(2) The horizontal distance along the takeoff path from the start of the takeoff to the point at which the airplane is 15 feet above the takeoff surface, achieved in a manner consistent with the achievement of V2 before reaching 35 feet above the takeoff surface, determined under § 25.111 for a wet runway.
(c) If the takeoff distance does not include a clearway, the takeoff run is equal to the takeoff distance. If the takeoff distance includes a clearway—
(1) The takeoff run on a dry runway is the greater of—
(i) The horizontal distance along the takeoff path from the start of the takeoff to a point equidistant between the point at which VLOF is reached and the point at which the airplane is 35 feet above the takeoff surface, as determined under § 25.111 for a dry runway; or
(ii) 115 percent of the horizontal distance along the takeoff path, with all engines operating, from the start of the takeoff to a point equidistant between the point at which VLOF is reached and the point at which the airplane is 35 feet above the takeoff surface, determined by a procedure consistent with § 25.111.
(2) The takeoff run on a wet runway is the greater of—
(i) The horizontal distance along the takeoff path from the start of the takeoff to the point at which the airplane is 15 feet above the takeoff surface, achieved in a manner consistent with the achievement of V2 before reaching 35 feet above the takeoff surface, as determined under § 25.111 for a wet runway; or
(ii) 115 percent of the horizontal distance along the takeoff path, with all engines operating, from the start of the takeoff to a point equidistant between the point at which VLOF is reached and the point at which the airplane is 35 feet above the takeoff surface, determined by a procedure consistent with § 25.111.

#### #42: Landing Climb (Functional)
In the landing configuration, the steady gradient of climb may not be less than 3.2 percent, with the engines at the power or thrust that is available 8 seconds after initiation of movement of the power or thrust controls from the minimum flight idle to the go-around power or thrust setting—
(a) In non-icing conditions, with a climb speed of VREF determined in accordance with § 25.125(b)(2)(i); and
(b) In icing conditions with the most critical of the landing ice accretion(s) defined in Appendices C and O of this part, as applicable, in accordance with § 25.21(g), and with a climb speed of VREF determined in accordance with § 25.125(b)(2)(ii).

#### #43: Climb One Engine Inoperative (OEI) (Functional)
(a) Takeoff; landing gear extended. In the critical takeoff configuration existing along the flight path (between the points at which the airplane reaches VLOF and at which the landing gear is fully retracted) and in the configuration used in § 25.111 but without ground effect, the steady gradient of climb must be positive for two-engine airplanes, and not less than 0.3 percent for three-engine airplanes or 0.5 percent for four-engine airplanes, at VLOF and with—
(1) The critical engine inoperative and the remaining engines at the power or thrust available when retraction of the landing gear is begun in accordance with § 25.111 unless there is a more critical power operating condition existing later along the flight path but before the point at which the landing gear is fully retracted; and
(2) The weight equal to the weight existing when retraction of the landing gear is begun, determined under § 25.111.
(b) Takeoff; landing gear retracted. In the takeoff configuration existing at the point of the flight path at which the landing gear is fully retracted, and in the configuration used in § 25.111 but without ground effect:
(1) The steady gradient of climb may not be less than 2.4 percent for two-engine airplanes, 2.7 percent for three-engine airplanes, and 3.0 percent for four-engine airplanes, at V2 with:
(i) The critical engine inoperative, the remaining engines at the takeoff power or thrust available at the time the landing gear is fully retracted, determined under § 25.111, unless there is a more critical power operating condition existing later along the flight path but before the point where the airplane reaches a height of 400 feet above the takeoff surface; and
(ii) The weight equal to the weight existing when the airplane's landing gear is fully retracted, determined under § 25.111.
(2) The requirements of paragraph (b)(1) of this section must be met:
(i) In non-icing conditions; and
(ii) In icing conditions with the most critical of the takeoff ice accretion(s) defined in Appendices C and O of this part, as applicable, in accordance with § 25.21(g), if in the configuration used to show compliance with § 25.121(b) with this takeoff ice accretion:
(A) The stall speed at maximum takeoff weight exceeds that in non-icing conditions by more than the greater of 3 knots CAS or 3 percent of VSR; or
(B) The degradation of the gradient of climb determined in accordance with § 25.121(b) is greater than one-half of the applicable actual-to-net takeoff flight path gradient reduction defined in § 25.115(b).
(c) Final takeoff. In the en route configuration at the end of the takeoff path determined in accordance with § 25.111:
(1) The steady gradient of climb may not be less than 1.2 percent for two-engine airplanes, 1.5 percent for three-engine airplanes, and 1.7 percent for four-engine airplanes, at VFTO with—
(i) The critical engine inoperative and the remaining engines at the available maximum continuous power or thrust; and
(ii) The weight equal to the weight existing at the end of the takeoff path, determined under § 25.111.
(2) The requirements of paragraph (c)(1) of this section must be met:
(i) In non-icing conditions; and
(ii) In icing conditions with the most critical of the final takeoff ice accretion(s) defined in Appendices C and O of this part, as applicable, in accordance with § 25.21(g), if in the configuration used to show compliance with § 25.121(b) with the takeoff ice accretion used to show compliance with § 25.111(c)(5)(i):
(A) The stall speed at maximum takeoff weight exceeds that in non-icing conditions by more than the greater of 3 knots CAS or 3 percent of VSR; or
(B) The degradation of the gradient of climb determined in accordance with § 25.121(b) is greater than one-half of the applicable actual-to-net takeoff flight path gradient reduction defined in § 25.115(b).
(d) Approach. In a configuration corresponding to the normal all-engines-operating procedure in which VSR for this configuration does not exceed 110 percent of the VSR for the related all-engines-operating landing configuration:
(1) The steady gradient of climb may not be less than 2.1 percent for two-engine airplanes, 2.4 percent for three-engine airplanes, and 2.7 percent for four-engine airplanes, with—
(i) The critical engine inoperative, the remaining engines at the go-around power or thrust setting;
(ii) The maximum landing weight;
(iii) A climb speed established in connection with normal landing procedures, but not exceeding 1.4 VSR; and
(iv) Landing gear retracted.
(2) The requirements of paragraph (d)(1) of this section must be met:
(i) In non-icing conditions; and
(ii) In icing conditions with the most critical of the approach ice accretion(s) defined in Appendices C and O of this part, as applicable, in accordance with § 25.21(g). The climb speed selected for non-icing conditions may be used if the climb speed for icing conditions, computed in accordance with paragraph (d)(1)(iii) of this section, does not exceed that for non-icing conditions by more than the greater of 3 knots CAS or 3 percent.

#### #44: Landing General (Functional)
(a) The horizontal distance necessary to land and to come to a complete stop (or to a speed of approximately 3 knots for water landings) from a point 50 feet above the landing surface must be determined (for standard temperatures, at each weight, altitude, and wind within the operational limits established by the applicant for the airplane):
(1) In non-icing conditions; and
(2) In icing conditions with the most critical of the landing ice accretion(s) defined in Appendices C and O of this part, as applicable, in accordance with § 25.21(g), if VREF for icing conditions exceeds VREF for non-icing conditions by more than 5 knots CAS at the maximum landing weight.
(b) In determining the distance in paragraph (a) of this section:
(1) The airplane must be in the landing configuration.
(2) A stabilized approach, with a calibrated airspeed of not less than VREF, must be maintained down to the 50-foot height.
(i) In non-icing conditions, VREF may not be less than:
(A) 1.23 VSR0;
(B) VMCL established under § 25.149(f); and
(C) A speed that provides the maneuvering capability specified in § 25.143(h).
(ii) In icing conditions, VREF may not be less than:
(A) The speed determined in paragraph (b)(2)(i) of this section;
(B) 1.23 VSR0 with the most critical of the landing ice accretion(s) defined in Appendices C and O of this part, as applicable, in accordance with § 25.21(g), if that speed exceeds VREF selected for non-icing conditions by more than 5 knots CAS; and
(C) A speed that provides the maneuvering capability specified in § 25.143(h) with the most critical of the landing ice accretion(s) defined in Appendices C and O of this part, as applicable, in accordance with § 25.21(g).
(3) Changes in configuration, power or thrust, and speed, must be made in accordance with the established procedures for service operation.
(4) The landing must be made without excessive vertical acceleration, tendency to bounce, nose over, ground loop, porpoise, or water loop.
(5) The landings may not require exceptional piloting skill or alertness.
(c) For landplanes and amphibians, the landing distance on land must be determined on a level, smooth, dry, hard-surfaced runway. In addition—
(1) The pressures on the wheel braking systems may not exceed those specified by the brake manufacturer;
(2) The brakes may not be used so as to cause excessive wear of brakes or tires; and
(3) Means other than wheel brakes may be used if that means—
(i) Is safe and reliable;
(ii) Is used so that consistent results can be expected in service; and
(iii) Is such that exceptional skill is not required to control the airplane.
(d) For seaplanes and amphibians, the landing distance on water must be determined on smooth water.
(e) For skiplanes, the landing distance on snow must be determined on smooth, dry, snow.
(f) The landing distance data must include correction factors for not more than 50 percent of the nominal wind components along the landing path opposite to the direction of landing, and not less than 150 percent of the nominal wind components along the landing path in the direction of landing.
(g) If any device is used that depends on the operation of any engine, and if the landing distance would be noticeably increased when a landing is made with that engine inoperative, the landing distance must be determined with that engine inoperative unless the use of compensating means will result in a landing distance not more than that with each engine operating.

#### #45: Longitudinal Control (Functional)
(a) It must be possible, at any point between the trim speed prescribed in § 25.103(b)(6) and stall identification (as defined in § 25.201(d)), to pitch the nose downward so that the acceleration to this selected trim speed is prompt with
(1) The airplane trimmed at the trim speed prescribed in § 25.103(b)(6);
(2) The landing gear extended;
(3) The wing flaps
(i) retracted and
(ii) extended; and
(4) Power
(i) off and
(ii) at maximum continuous power on the engines.
(b) With the landing gear extended, no change in trim control, or exertion of more than 50 pounds control force (representative of the maximum short term force that can be applied readily by one hand) may be required for the following maneuvers:
(1) With power off, flaps retracted, and the airplane trimmed at 1.3 VSR1, extend the flaps as rapidly as possible while maintaining the airspeed at approximately 30 percent above the reference stall speed existing at each instant throughout the maneuver.
(2) Repeat paragraph (b)(1) except initially extend the flaps and then retract them as rapidly as possible.
(3) Repeat paragraph (b)(2), except at the go-around power or thrust setting.
(4) With power off, flaps retracted, and the airplane trimmed at 1.3 VSR1, rapidly set go-around power or thrust while maintaining the same airspeed.
(5) Repeat paragraph (b)(4) except with flaps extended.
(6) With power off, flaps extended, and the airplane trimmed at 1.3 VSR1, obtain and maintain airspeeds between VSW and either 1.6 VSR1 or VFE, whichever is lower.
(c) It must be possible, without exceptional piloting skill, to prevent loss of altitude when complete retraction of the high lift devices from any position is begun during steady, straight, level flight at 1.08 VSR1 for propeller powered airplanes, or 1.13 VSR1 for turbojet powered airplanes, with—
(1) Simultaneous movement of the power or thrust controls to the go-around power or thrust setting;
(2) The landing gear extended; and
(3) The critical combinations of landing weights and altitudes.
(d) If gated high-lift device control positions are provided, paragraph (c) of this section applies to retractions of the high-lift devices from any position from the maximum landing position to the first gated position, between gated positions, and from the last gated position to the fully retracted position. The requirements of paragraph (c) of this section also apply to retractions from each approved landing position to the control position(s) associated with the high-lift device configuration(s) used to establish the go-around procedure(s) from that landing position. In addition, the first gated control position from the maximum landing position must correspond with a configuration of the high-lift devices used to establish a go-around procedure from a landing configuration. Each gated control position must require a separate and distinct motion of the control to pass through the gated position and must have features to prevent inadvertent movement of the control through the gated position. It must only be possible to make this separate and distinct motion once the control has reached the gated position.

#### #46: Lateral and Directional Control (Functional)
(a) Directional control; general. It must be possible, with the wings level, to yaw into the operative engine and to safely make a reasonably sudden change in heading of up to 15 degrees in the direction of the critical inoperative engine. This must be shown at 1.3 VSR1 for heading changes up to 15 degrees (except that the heading change at which the rudder pedal force is 150 pounds need not be exceeded), and with—
(1) The critical engine inoperative and its propeller in the minimum drag position;
(2) The power required for level flight at 1.3 VSR1, but not more than maximum continuous power;
(3) The most unfavorable center of gravity;
(4) Landing gear retracted;
(5) Flaps in the approach position; and
(6) Maximum landing weight.
(b) Directional control; airplanes with four or more engines. Airplanes with four or more engines must meet the requirements of paragraph (a) of this section except that—
(1) The two critical engines must be inoperative with their propellers (if applicable) in the minimum drag position;
(2) [Reserved]
(3) The flaps must be in the most favorable climb position.
(c) Lateral control; general. It must be possible to make 20° banked turns, with and against the inoperative engine, from steady flight at a speed equal to 1.3 VSR1, with—
(1) The critical engine inoperative and its propeller (if applicable) in the minimum drag position;
(2) The remaining engines at maximum continuous power;
(3) The most unfavorable center of gravity;
(4) Landing gear
(i) retracted and
(ii) extended;
(5) Flaps in the most favorable climb position; and
(6) Maximum takeoff weight.
(d) Lateral control; roll capability. With the critical engine inoperative, roll response must allow normal maneuvers. Lateral control must be sufficient, at the speeds likely to be used with one engine inoperative, to provide a roll rate necessary for safety without excessive control forces or travel.
(e) Lateral control; airplanes with four or more engines. Airplanes with four or more engines must be able to make 20° banked turns, with and against the inoperative engines, from steady flight at a speed equal to 1.3 VSR1, with maximum continuous power, and with the airplane in the configuration prescribed by paragraph (b) of this section.
(f) Lateral control; all engines operating. With the engines operating, roll response must allow normal maneuvers (such as recovery from upsets produced by gusts and the initiation of evasive maneuvers). There must be enough excess lateral control in sideslips (up to sideslip angles that might be required in normal operation), to allow a limited amount of maneuvering and to correct for gusts. Lateral control must be enough at any speed up to VFC/MFC to provide a peak roll rate necessary for safety, without excessive control forces or travel.

#### #47: Minimum Control Speed (Functional)
(a) In establishing the minimum control speeds required by this section, the method used to simulate critical engine failure must represent the most critical mode of powerplant failure with respect to controllability expected in service.
(b) VMC is the calibrated airspeed at which, when the critical engine is suddenly made inoperative, it is possible to maintain control of the airplane with that engine still inoperative and maintain straight flight with an angle of bank of not more than 5 degrees.
(c) VMC may not exceed 1.13 VSR with—
(1) Maximum available takeoff power or thrust on the engines;
(2) The most unfavorable center of gravity;
(3) The airplane trimmed for takeoff;
(4) The maximum sea level takeoff weight (or any lesser weight necessary to show VMC);
(5) The airplane in the most critical takeoff configuration existing along the flight path after the airplane becomes airborne, except with the landing gear retracted;
(6) The airplane airborne and the ground effect negligible; and
(7) If applicable, the propeller of the inoperative engine—
(i) Windmilling;
(ii) In the most probable position for the specific design of the propeller control; or
(iii) Feathered, if the airplane has an automatic feathering device acceptable for showing compliance with the climb requirements of § 25.121.
(d) The rudder forces required to maintain control at VMC may not exceed 150 pounds nor may it be necessary to reduce power or thrust of the operative engines. During recovery, the airplane may not assume any dangerous attitude or require exceptional piloting skill, alertness, or strength to prevent a heading change of more than 20 degrees.
(e) VMCG, the minimum control speed on the ground, is the calibrated airspeed during the takeoff run at which, when the critical engine is suddenly made inoperative, it is possible to maintain control of the airplane using the rudder control alone (without the use of nosewheel steering), as limited by 150 pounds of force, and the lateral control to the extent of keeping the wings level to enable the takeoff to be safely continued using normal piloting skill. In the determination of VMCG, assuming that the path of the airplane accelerating with all engines operating is along the centerline of the runway, its path from the point at which the critical engine is made inoperative to the point at which recovery to a direction parallel to the centerline is completed may not deviate more than 30 feet laterally from the centerline at any point. VMCG must be established with—
(1) The airplane in each takeoff configuration or, at the option of the applicant, in the most critical takeoff configuration;
(2) Maximum available takeoff power or thrust on the operating engines;
(3) The most unfavorable center of gravity;
(4) The airplane trimmed for takeoff; and
(5) The most unfavorable weight in the range of takeoff weights.
(f) VMCL, the minimum control speed during approach and landing with all engines operating, is the calibrated airspeed at which, when the critical engine is suddenly made inoperative, it is possible to maintain control of the airplane with that engine still inoperative, and maintain straight flight with an angle of bank of not more than 5 degrees. VMCL must be established with—
(1) The airplane in the most critical configuration (or, at the option of the applicant, each configuration) for approach and landing with all engines operating;
(2) The most unfavorable center of gravity;
(3) The airplane trimmed for approach with all engines operating;
(4) The most favorable weight, or, at the option of the applicant, as a function of weight;
(5) For propeller airplanes, the propeller of the inoperative engine in the position it achieves without pilot action, assuming the engine fails while at the power or thrust necessary to maintain a three degree approach path angle; and
(6) Go-around power or thrust setting on the operating engine(s).
(g) For airplanes with three or more engines, VMCL-2, the minimum control speed during approach and landing with one critical engine inoperative, is the calibrated airspeed at which, when a second critical engine is suddenly made inoperative, it is possible to maintain control of the airplane with both engines still inoperative, and maintain straight flight with an angle of bank of not more than 5 degrees. VMCL-2 must be established with—
(1) The airplane in the most critical configuration (or, at the option of the applicant, each configuration) for approach and landing with one critical engine inoperative;
(2) The most unfavorable center of gravity;
(3) The airplane trimmed for approach with one critical engine inoperative;
(4) The most unfavorable weight, or, at the option of the applicant, as a function of weight;
(5) For propeller airplanes, the propeller of the more critical inoperative engine in the position it achieves without pilot action, assuming the engine fails while at the power or thrust necessary to maintain a three degree approach path angle, and the propeller of the other inoperative engine feathered;
(6) The power or thrust on the operating engine(s) necessary to maintain an approach path angle of three degrees when one critical engine is inoperative; and
(7) The power or thrust on the operating engine(s) rapidly changed, immediately after the second critical engine is made inoperative, from the power or thrust prescribed in paragraph (g)(6) of this section to—
(i) Minimum power or thrust; and
(ii) Go-around power or thrust setting.
(h) In demonstrations of VMCL and VMCL-2—
(1) The rudder force may not exceed 150 pounds;
(2) The airplane may not exhibit hazardous flight characteristics or require exceptional piloting skill, alertness, or strength;
(3) Lateral control must be sufficient to roll the airplane, from an initial condition of steady flight, through an angle of 20 degrees in the direction necessary to initiate a turn away from the inoperative engine(s), in not more than 5 seconds; and
(4) For propeller airplanes, hazardous flight characteristics must not be exhibited due to any propeller position achieved when the engine fails or during any likely subsequent movements of the engine or propeller controls.

#### #48: Static Longitudinal Stability (Functional)
Under the conditions specified in § 25.175, the characteristics of the elevator control forces (including friction) must be as follows:
(a) A pull must be required to obtain and maintain speeds below the specified trim speed, and a push must be required to obtain and maintain speeds above the specified trim speed. This must be shown at any speed that can be obtained except speeds higher than the landing gear or wing flap operating limit speeds or VFC/MFC, whichever is appropriate, or lower than the minimum speed for steady unstalled flight.
(b) The airspeed must return to within 10 percent of the original trim speed for the climb, approach, and landing conditions specified in § 25.175 (a), (c), and (d), and must return to within 7.5 percent of the original trim speed for the cruising condition specified in § 25.175(b), when the control force is slowly released from any speed within the range specified in paragraph (a) of this section.
(c) The average gradient of the stable slope of the stick force versus speed curve may not be less than 1 pound for each 6 knots.
(d) Within the free return speed range specified in paragraph (b) of this section, it is permissible for the airplane, without control forces, to stabilize on speeds above or below the desired trim speeds if exceptional attention on the part of the pilot is not required to return to and maintain the desired trim speed and altitude.

#### #49: Static Lateral Directional Stability (Functional)
(a) The static directional stability (as shown by the tendency to recover from a skid with the rudder free) must be positive for any landing gear and flap position and symmetric power condition, at speeds from 1.13 VSR1, up to VFE, VLE, or VFC/MFC (as appropriate for the airplane configuration).
(b) The static lateral stability (as shown by the tendency to raise the low wing in a sideslip with the aileron controls free) for any landing gear and flap position and symmetric power condition, may not be negative at any airspeed (except that speeds higher than VFE need not be considered for flaps extended configurations nor speeds higher than VLE for landing gear extended configurations) in the following airspeed ranges:
(1) From 1.13 VSR1 to VMO/MMO.
(2) From VMO/MMO to VFC/MFC, unless the divergence is—
(i) Gradual;
(ii) Easily recognizable by the pilot; and
(iii) Easily controllable by the pilot.
(c) The following requirement must be met for the configurations and speed specified in paragraph (a) of this section. In straight, steady sideslips over the range of sideslip angles appropriate to the operation of the airplane, the aileron and rudder control movements and forces must be substantially proportional to the angle of sideslip in a stable sense. This factor of proportionality must lie between limits found necessary for safe operation. The range of sideslip angles evaluated must include those sideslip angles resulting from the lesser of:
(1) One-half of the available rudder control input; and
(2) A rudder control force of 180 pounds.
(d) For sideslip angles greater than those prescribed by paragraph (c) of this section, up to the angle at which full rudder control is used or a rudder control force of 180 pounds is obtained, the rudder control forces may not reverse, and increased rudder deflection must be needed for increased angles of sideslip. Compliance with this requirement must be shown using straight, steady sideslips, unless full lateral control input is achieved before reaching either full rudder control input or a rudder control force of 180 pounds; a straight, steady sideslip need not be maintained after achieving full lateral control input. This requirement must be met at all approved landing gear and flap positions for the range of operating speeds and power conditions appropriate to each landing gear and flap position with all engines operating.

#### #50: Dynamic Stability (Functional)
(a) Any short period oscillation, not including combined lateral-directional oscillations, occurring between 1.13 VSR and maximum allowable speed appropriate to the configuration of the airplane must be heavily damped with the primary controls—
(1) Free; and
(2) In a fixed position.
(b) Any combined lateral-directional oscillations (“Dutch roll”) occurring between 1.13 VSR and maximum allowable speed appropriate to the configuration of the airplane must be positively damped with controls free, and must be controllable with normal use of the primary controls without requiring exceptional pilot skill.

#### #51 (Functional)
(a) It must be possible to produce and to correct roll and yaw by unreversed use of the aileron and rudder controls, up to the time the airplane is stalled. No abnormal nose-up pitching may occur. The longitudinal control force must be positive up to and throughout the stall. In addition, it must be possible to promptly prevent stalling and to recover from a stall by normal use of the controls.
(b) For level wing stalls, the roll occurring between the stall and the completion of the recovery may not exceed approximately 20 degrees.
(c) For turning flight stalls, the action of the airplane after the stall may not be so violent or extreme as to make it difficult, with normal piloting skill, to effect a prompt recovery and to regain control of the airplane. The maximum bank angle that occurs during the recovery may not exceed—
(1) Approximately 60 degrees in the original direction of the turn, or 30 degrees in the opposite direction, for deceleration rates up to 1 knot per second; and
(2) Approximately 90 degrees in the original direction of the turn, or 60 degrees in the opposite direction, for deceleration rates in excess of 1 knot per second.

### #15: Certifiable Date (Functional)
All components, including engines, must be certifiable by 2034

### #16: Entry Into Service (Functional)
Target EIS: 2035

## #17: Operations (Functional)

### #18: Icing Conditions (Functional)
Capable of safe operation in known icing conditions

## #31: SAF Compatible (Functional)
Aircraft shall be compatible with sustainable aviation fuel (SAF).

## #32: Cabin Comfort (Functional)
Aircraft shall contain cabin comfort features including stand-up cabin height for majority of passengers and overhead bins sized for standard carry-ons. (Cabin height > 6)

## #33: Flexible Seating Layout (Functional)
Aircraft shall have flexible two or three-class seating layouts available.

## #52: Cruise CD (Functional)
CD<0.015 at cruise

## #53: Subsystem Power (Functional)
Electrical systems run on 115 VAC 400Hz

## #55: Cabin Altitude (Functional)
Cabin altitude shall be 6000 ft at cruise

## #58: Yearly Service Time (Functional)
Aircraft shall be capable of flying 3000 hrs/yr

## #59: Cruise Altitude (Functional)
Aircraft shall perform normal cruise operations successfuly at an altitude of at least 50,000 ft.

## #60: Climb Rate (Functional)
Aircraft shall climb to cruising altitude at a rate of at least 3000 ft/min

## #61: Sup LD (Functional)
Aircraft shall have a supersonic L/D of 7.5.

## #62: Sub LD (Functional)
Aircraft shall have a subsonic L/D of 11.5

## #64: Supercruise Engines (Functional)
Aircraft shall have supercruise capable engines.

## #72: Tail Stall (Functional)
The aircraft's tail shall stall at a greater angle of attack than the main wings.

## #73: Tail Crit Mach (Functional)
The aircraft's tail shall have a greater critical mach number than that of the main wings.

## #74: Skin Temp (Functional)
Aircraft's outer skin shall withstand temperatures of up to 370 C

## #75: Object Impact (Functional)
Aircraft's structure shall be capable of withstanding impact from 8lb object at supersonic speeds.

## #76: MTOW (Functional)
Aircraft shall have a maximum takeoff wheight no larger than 400,000 lbs.

## #77: Max Wing Loading (Functional)
Aircraft's wings shall be capable of withstanding loading of 1000 lb/ft^2 at 3% thickness.

## #78: Sink Rate (Functional)
Aircraft shall be capable of withstanding a landing with a sink rate of at least 10 ft/s.

## #79: Stability (Functional)
Aircraft shall be stable and controllable

### #54: Fly-By-Wire (Functional)
Fly-by-wire system trims aircraft to maintain net zero forces and moments in steady level flight.

### #63: Crosswind Landing (Functional)
Aircraft shall be able to land in a crosswind of 40 mph.

### #68: Longitudinal Stability (Functional)
Aircraft's Longitudinal stability derivative shall be negative.

### #69: SM (Functional)
Aircraft's static margin shall stay between 4 and 7% during operation.

### #70: Directional Stability (Functional)
Aircraft's directional stability derivative shall be positive.

### #71: Lateral Stability (Functional)
Aircraft's lateral stability derivative shall be negative.

### #83: Longitudinal Stability (Functional)
Aircraft's Longitudinal stability derivative shall be negative.

## #80: Powerplant Service (Functional)
Powerplant service interval requirements

### #65: Comp/Turb blade Service Life (Functional)
Compressor and turbine blades should have a service life of 12,000 flight hours.

### #66: Engine Service Life (Functional)
Aircraft's engines should have a service life of at least 27,000 flight hours.

### #67: Engine Change Time (Functional)
Engine change time shall be less than 1.5 hours.

## #81: Cost (Functional)
Aircraft cost

### #56: Breakeven Cost (Functional)
Aircraft shall have a breakeven cost equivalent to 860 units.

### #57: Operating Cost (Functional)
Direct operating cost shall be less than $0.30 seat-nm.
